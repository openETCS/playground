# Specification: Specification Document
- Description: Requirements Document

## 7.6 (Headline Type)
Language and formalism

## R-WP2/D2.6-02-065 (Requirement Type)
The description of the SFM shall be understandable by domain experts with a reasonable amount of specific training.

### R-WP2/D2.6-02-065.01 (Requirement Type)
The means of description of the SFM shall provide simple graphicalrepresentation for component relations, data-flow and system behavior (which cover process sequence and state evolution).

### R-WP2/D2.6-02-065.02 (Requirement Type)
The means of description of the SFM shall provide visual simulation of the system behavior.

## R-WP2/D2.6-02-066 (Requirement Type)
The means of discription used to formalize safety properties shall be formal and declarative.

### R-WP2/D2.6-02-066.01 (Requirement Type)
The formalism shall be understandable by domain experts without specific training.

### R-WP2/D2.6-02-066.02 (Requirement Type)
The formalism shall be able to state:

#### R-WP2/D2.6-02-066.02.01 (Requirement Type)
logical statements,

#### R-WP2/D2.6-02-066.02.02 (Requirement Type)
time constraints.

## R-WP2/D2.6-02-067 (Requirement Type)
All means of description used shall be standardized or at least documented in detailed.

## R-WP2/D2.6-02-068 (Requirement Type)
The means of descriptions used for SSRS, SFM and FFM modeling shall be open for the use with different tool via:

### R-WP2/D2.6-02-068.01 (Requirement Type)
direct exchange of the model data file;

### R-WP2/D2.6-02-068.02 (Requirement Type)
or fully automated translation of the model data file.

## R-WP2/D2.6-02-069 (Requirement Type)
The means of description for the SFM shall be able to formalize:

### R-WP2/D2.6-02-069.01 (Requirement Type)
State machines,

### R-WP2/D2.6-02-069.02 (Requirement Type)
Time-outs,

### R-WP2/D2.6-02-069.03 (Requirement Type)
Truth tables,

### R-WP2/D2.6-02-069.04 (Requirement Type)
Arithmetics,

### R-WP2/D2.6-02-069.05 (Requirement Type)
Braking curves,

### R-WP2/D2.6-02-069.06 (Requirement Type)
Logical statements,

### R-WP2/D2.6-02-069.07 (Requirement Type)
Messages and fields.

## R-WP2/D2.6-02-070 (Requirement Type)
The language for the FFM shall be able to formalize as much as possible of:

### R-WP2/D2.6-02-070.01 (Requirement Type)
State machines,

### R-WP2/D2.6-02-070.02 (Requirement Type)
Time-outs,

### R-WP2/D2.6-02-070.03 (Requirement Type)
Truth tables,

### R-WP2/D2.6-02-070.04 (Requirement Type)
Arithmetics,

### R-WP2/D2.6-02-070.05 (Requirement Type)
Braking curves,

### R-WP2/D2.6-02-070.06 (Requirement Type)
Logical statements,

### R-WP2/D2.6-02-070.07 (Requirement Type)
Messages and fields.

### R31 (Comment Type)
Comment. These requirements do not state that all these objects need to be first order objects of the language. They only state that it should be possible to formalize and manipulate them. It is to be noted that if (for example) braking curves are objects of the language, it shall be proved that they are sound, and that the code generation for these objects is also sound.

## R-WP2/D2.6-02-071 (Requirement Type)
The mean of description of the SFM shall allow it to be simulable.

### R33 (Comment Type)
Comment. This requirement is in the section “language and formalism” because in order for the model to be simulable, it has to be able to yield some algorithmic content and determinism (or a way of determining a non-deterministic model), which is indeed a property on the formal aspects of the model. In the other hand, it is also a requirement on the tool chain, hence there are also some requirements on this topic in Sect. 7.7.

## R-WP2/D2.6-02-072 (Requirement Type)
It shall be possible to assert logical properties on the SFM and FFM (e.g. invariants).

### R-WP2/D2.6-02-072.01 (Requirement Type)
It shall be possible to check the conformance of these properties at runtime on the SFM.

### R-WP2/D2.6-02-072.02 (Requirement Type)
It shall be possible to prove the conformance of the FFM to these properties.

## R-WP2/D2.6-02-073 (Requirement Type)
The language and formalism should be extensible.

## 7.7 (Headline Type)
Tools chain

### 7.7.1 (Headline Type)
Usage

## R-WP2/D2.6-02-074 (Requirement Type)
The tools chain shall be composed as far as possible of Open Source components licensed under a license compatible with the EUPL license.

### R-WP2/D2.6-02-074.01 (Requirement Type)
Closed source components may be used, but only if their use is not mandatory in the process, or if an open source counterpart is provided.

### R-WP2/D2.6-02-074.02 (Requirement Type)
If a closed source component is used, it has to be displayed how an open source component has to be designed to replace the closed component later.

## R-WP2/D2.6-02-075 (Requirement Type)
The tools chain shall be portable to common operating systems.

### R-WP2/D2.6-02-075.01 (Requirement Type)
The tool chain shall run stable on all main operating systems.

### R-WP2/D2.6-02-075.02 (Requirement Type)
The tool chain shall run with a good performance on all main operating systems.

### R-WP2/D2.6-02-075.03 (Requirement Type)
The tool chain shall run on at least one major open source operating system.

## R-WP2/D2.6-02-076 (Requirement Type)
The tools used in the tool chain shall be able to cooperate, i.e. the outputs of one tool will be suitable to be used as the inputs of another tool.

### R-WP2/D2.6-02-076.01 (Requirement Type)
All possible input and output formats of a tool have to be documented.

### R-WP2/D2.6-02-076.02 (Requirement Type)
Open data formats shall be used for data exchange.

## R-WP2/D2.6-01-032 (Requirement Type)
If tools are required for configuration management, they will be considered as part of the tool chain.

## R-WP2/D2.6-02-077 (Requirement Type)
The tools chain shall allow to generate executable code from the model(s).

### R52 (Headline Type)

## R17 (Comment Type)
jhgjhghjh
