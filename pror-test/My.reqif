# Specification: Specification Document
- Description: Functions

## 4.5.2.1 (Function Type)
Roll_Away_Protection
- Subset-Link -> R4

### R5 (Variable Type)
MOTION_DIRECTION
- Direction: Output

# Specification
- Description: Subset-026

## R3 (Requirement Type)
4.5.2.1 Roll Away Protection

### R4 (Requirement Type)
3.14.2 (Related SRS)

## R1 (Requirement Type)
Roll_Away_Protection
